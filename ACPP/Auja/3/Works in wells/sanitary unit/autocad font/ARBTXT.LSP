(vmon)

(defun renviron_ ()
       (setvar "BLIPMODE" blp_)
       (setvar "HIGHLIGHT" hgh_)
       (setvar "LIMCHECK" lim_)
       (setvar "CMDECHO" cm)
)

;(defun *error* (s)
;       (repeat (1+ wch_) (entdel (entlast)))
;       (renviron_)
;)

(defun wrtr_()
       (entdel (entlast))
       (setq pt1_ (strcat outline_ (chr 127) (chr 45)))
       (command "text" p_ size_ ang_ pt1_)
)

(defun counter_ (/ tcnt_)
         (setq cntr_ 0)
         (setq tcnt_ (strcat (chr 127) "1"))
         (while (member (ascii (substr tcnt_ 2 1)) number_)
            (setq tcnt_ (substr inline_ (- (1- (strlen inline_)) cntr_) 2))
            (if (= (+ cntr_ 2) (strlen inline_)) 
             (setq tcnt_ (strcat (chr 127) (chr 127)))
            )
            (setq cntr_ (+ cntr_ 2))
         )
         (setq cntr_ (- cntr_ 2))
)

(defun drct_()
      (setq inline_  (strcat inline_  (chr 127) (chr g)))
      (setq outline_ (strcat outline_ (chr 127) (chr g)))
)

(defun adnum_ (/ ln_ bgn_ edn_ sdr_ ajz_)
         (setq ln_ (strlen inline_))
         (setq bgn_ (substr inline_ 1 (- ln_ cntr_)))
         (setq edn_ (substr inline_ (1+ (- ln_ cntr_)) cntr_))
         (setq sdr_ (substr outline_ 1 (- ln_ cntr_)))
         (setq ajz_ (substr outline_ (1+ (- ln_ cntr_)) cntr_))
         (setq inline_  (strcat bgn_ (chr 127) (chr g) edn_))
         (setq outline_ (strcat sdr_ (chr 127) (chr g) ajz_))
)

(defun shift_ ()
         (setq inline_  (strcat (chr 127) (chr g)  inline_))
         (setq outline_ (strcat (chr 127) (chr g) outline_))
)

(defun num_ ()
         (counter_)
         (cond ((= cntr_ 0) (drct_))
               ((= cntr_ (- (strlen inline_) 2)) (shift_))
               (t (adnum_))
         )
         (wrtr_)
)

(defun find_(asky_ loc)
       (cond ((not (member asky_ lett_)) asky_)
             ((= asky_ 104) (nth loc '(239 238 240 104)))
             ((= asky_ 102) (nth loc '(146 145 147 102)))
             ((= asky_ 106) (nth loc '(158 157 159 106)))
             ((= asky_ 101) (nth loc '(143 142 144 101)))
             ((= asky_  91) (nth loc '(209 208 210 091)))
             ((= asky_ 112) (nth loc '(176 175 177 112)))
             ((= asky_ 111) (nth loc '(173 172 174 111)))
             ((= asky_  93) (nth loc '(215 214 216 093)))
             ((= asky_  96) (nth loc '(212 211 213 092)))
             ((= asky_ 118) (nth loc '(194 193 195 118)))
             ((= asky_  46) (nth loc '(224 223 225 046)))
             ((= asky_ 115) (nth loc '(185 184 186 115)))
             ((= asky_  97) (nth loc '(131 130 132 097)))
             ((= asky_ 119) (nth loc '(197 196 198 119)))
             ((= asky_ 113) (nth loc '(179 178 180 113)))
             ((= asky_  39) (nth loc '(218 217 219 039)))
             ((= asky_  47) (nth loc '(227 226 228 047)))
             ((= asky_ 117) (nth loc '(191 190 192 117)))
             ((= asky_ 121) (nth loc '(203 202 204 089)))
             ((= asky_ 116) (nth loc '(188 187 189 116)))
             ((= asky_ 114) (nth loc '(182 181 183 114)))
             ((= asky_  59) (nth loc '(230 229 231 059)))
             ((= asky_ 103) (nth loc '(236 235 237 103)))
             ((= asky_ 108) (nth loc '(164 163 165 108)))
             ((= asky_ 107) (nth loc '(161 160 162 107)))
             ((= asky_ 105) (nth loc '(155 154 156 105)))
             ((= asky_  44) (nth loc '(221 220 222 044)))
             ((= asky_ 100) (nth loc '(140 139 141 100)))
             ((= asky_ 109) (nth loc '(167 166 168 109)))
             ((= asky_ 122) (nth loc '(206 205 207 122)))
             ((= asky_  99) (nth loc '(137 136 138 099)))
             ((= asky_  98) (nth loc '(233 232 234 098)))
             ((= asky_  66) (nth loc '(134 133 135 134)))
             ((= asky_  72) (nth loc '(152 151 153 072)))
             ((= asky_  71) (nth loc '(149 148 150 071)))
             ((= asky_  78) (nth loc '(170 169 171 078)))
             ((= asky_ 120) (nth loc '(200 199 201 120)))
             ((= asky_ 110) (nth loc '(242 241 243 242)))
             ((= asky_  74) (nth loc '(246 245 247 247)))

             ((= asky_  33) (nth loc '(033 033 033 033)))
             ((= asky_  34) (nth loc '(034 034 034 034)))
             ((= asky_  35) (nth loc '(035 035 035 035)))
             ((= asky_  36) (nth loc '(036 036 036 036)))
             ((= asky_  37) (nth loc '(037 037 037 037)))
             ((= asky_  40) (nth loc '(040 040 040 040)))
             ((= asky_  41) (nth loc '(041 041 041 041)))
             ((= asky_  42) (nth loc '(042 042 042 042)))
             ((= asky_  43) (nth loc '(043 043 043 043)))
             ((= asky_  45) (nth loc '(045 045 045 045)))
             ((= asky_  58) (nth loc '(058 058 058 058)))
             ((= asky_  60) (nth loc '(060 060 060 060)))
             ((= asky_  61) (nth loc '(061 061 061 061)))
             ((= asky_  62) (nth loc '(062 062 062 062)))
             ((= asky_  63) (nth loc '(063 063 063 063)))
             ((= asky_  64) (nth loc '(064 064 064 064)))
             ((= asky_  65) (nth loc '(065 065 065 065)))
             ((= asky_  73) (nth loc '(073 073 073 073)))
             ((= asky_  75) (nth loc '(075 075 075 075)))
             ((= asky_  79) (nth loc '(079 079 079 079)))
             ((= asky_  80) (nth loc '(080 080 080 080)))
             ((= asky_  94) (nth loc '(094 094 094 094)))
             ((= asky_ 125) (nth loc '(096 096 096 096)))
             ((= asky_ 123) (nth loc '(126 126 126 126)))
             ((= asky_  81) (nth loc '(123 123 123 123)))
             ((= asky_  87) (nth loc '(125 125 125 125)))
             ((= asky_ 126) (nth loc '(124 124 124 124)))
             ((= asky_  88) (nth loc '(127 127 127 127)))
             ((= asky_  90) (nth loc '(128 128 128 128)))
             ((= asky_  83) (nth loc '(129 129 129 129)))
       )
)

(defun prune_ (/ dg_ ct_ term)
     (setq dg_ (ascii (substr inline_ (strlen inline_) 1)))
     (setq ct_ (if (member (ascii (substr inline_ (- (strlen inline_) 4) 1))
                          precat_) 2 3))
     (setq term (strcat (chr 127) (chr (find_ dg_ ct_))))
     (setq outline_ (strcat (substr outline_ 1 (- (strlen outline_) 4)) term))
)

(defun duo_ (/ ct_ term)
     (setq ct_ (if (member (ascii (substr inline_ 2 1)) precat_) 2 3))
     (setq term 
      (strcat (chr 127) (chr (find_ (ascii (substr inline_ 4 1)) ct_))))
     (setq outline_ (strcat (substr outline_ 1 2) term))
)

(defun una_ ()
     (setq outline_ 
      (strcat (chr 127) (chr (find_ (ascii (substr inline_ 2 1)) 3)))
     )
)

(defun deleter_ ()
     (setq inline_ (substr inline_ 1 (- (strlen inline_) 2)))
     (cond ((= (strlen inline_) 2) (una_))
           ((= (strlen inline_) 4) (duo_))
           (t (prune_))
     )
)

(defun denumber_ (/ ln_ bgn_ edn_ sdr_ ajz_)
        (counter_)
        (if (= cntr_ (strlen inline_))
            (progn
               (setq inline_  (substr inline_  3 (- (strlen  inline_) 2)))
               (setq outline_ (substr outline_ 3 (- (strlen outline_) 2)))
            )
            (progn
               (setq ln_ (strlen inline_))
               (setq bgn_ (substr inline_ 1 (- ln_ cntr_)))
               (setq edn_ (substr inline_ (+ 3 (- ln_ cntr_)) cntr_))
               (setq sdr_ (substr outline_ 1 (- ln_ cntr_)))
               (setq ajz_ (substr outline_ (+ 3 (- ln_ cntr_)) cntr_))
               (setq inline_ (strcat bgn_ edn_))
               (setq outline_ (strcat sdr_ ajz_))
            )
         )
)

(defun debranch_ (/ br)
      (setq br (ascii (substr inline_ (strlen inline_) 1)))
      (cond ((member br number_) (denumber_))
            ((member br lett_) (deleter_))
            (T                 (deleter_))
      )
)

(defun vanish_ ()
       (setq inline_ "")
       (setq outline_ "")
)

(defun up_ ()
       (if (= wch_ 0) t
           (progn
                (entdel (entlast))
                (setq wch_ (1- wch_))
                (setq inline_ (car ilst_)) (setq ilst_ (cdr ilst_))
                (setq outline_ (car olst_)) (setq olst_ (cdr olst_))
                (setq spnts_ (cdr spnts_)) (setq p_ (car spnts_))
           )
        )
)

(defun bsp_ ()
       (cond ((= (strlen inline_) 0) (up_))
             ((= (strlen inline_) 2) (vanish_))
             (t (debranch_))
       )
       (wrtr_)
)

;(defun second_(/ ps fchar schar)
;       (setq inline_ (strcat inline_ (chr g)))
;       (setq ps (if (member (ascii inline_) precat_) 2 3))
;       (setq fchar (chr (find_ (ascii inline_) 0)))
;       (setq schar (chr (find_ g ps)))
;       (setq outline_ (strcat fchar schar))
;)

(defun second_ ( / ps fchar schar ans)
 (setq inline_ (strcat inline_ (chr 127) (chr g)))
 (setq ps (if (member (ascii (substr inline_ 2 1)) precat_) 2 3))
 (setq fchar (chr (find_ (ascii (substr inline_ 2 1)) 0)))
 (setq schar (chr (find_ g ps)))
 (setq outline_ (strcat (chr 127) fchar (chr 127) schar))
)

(defun first_()
       (setq inline_ (strcat inline_ (chr 127) (chr g)))
       (setq outline_ (strcat (chr 127) (chr (find_ g 3))))
)

(defun strngr_(/ last posg blast posl one two)
       (setq last (ascii (substr inline_ (strlen inline_) 1)))
       (setq posg (if (member last precat_) 2 3))
       (setq blast (ascii (substr inline_ (- (strlen inline_) 2) 1)))
       (setq posl (if (member blast precat_) 1 0))
       (setq one (strcat (chr 127) (chr (find_ last posl))))
       (setq two (strcat (chr 127) (chr (find_ g posg))))
       (setq inline_ (strcat inline_ (chr 127) (chr g)))
       (setq outline_ 
        (strcat 
         (substr outline_ 1 (- (strlen outline_) 2)) one two
        )
       )
)

(defun litra_ ()
       (cond ((= (strlen inline_) 0) (first_))
             ((= (strlen inline_) 2) (second_))
             (t (strngr_))
       )
       (wrtr_)
)

(defun lefin_ (/ numero_)
       (repeat (1+ wch_) (entdel (entlast)))
       (setq olst_ (reverse olst_))
       (setq spnts_ (reverse (cdr spnts_)))
       (setq numero_ 0)
       (repeat wch_
               (setq p_ (nth numero_ spnts_))
               (setq txt (nth numero_ olst_))
               (eval final_)
               (setq numero_ (1+ numero_))
       )
       (setq sustain_ 0)
)

(defun getout_ ()
       (cond ((= format_ "Center") (centout_))
             ((= format_ "Middle") (midout))
             ((= (type format_) 'LIST) (lefin_))
       )
)

(defun ret_ ()
      (if (= (strlen inline_) 0) (getout_)
             (progn
                  (entdel (entlast))
                  (command "text" p_ size_ ang_ outline_)
                  (setq ilst_ (cons inline_ ilst_))
                  (setq olst_ (cons outline_ olst_))
                  (setq p_ (polar p_ (+ gang_ (/ pi 2)) (* 2 size_)))
                  (setq spnts_ (cons p_ spnts_))
                  (setq wch_ (1+ wch_))
                  (command "text" p_ size_ ang_ (strcat (chr 127) (chr 45)))
                  (setq inline_ "")
                  (setq outline_ "")
             )
       )
)

(defun pointer_ ()
    (entdel (entlast))
    (command "text" p_ size_ ang_ outline_)
    (setq p_ (cadr inp_))
    (command "text" p_ size_ ang_ (chr 219))
    (if (= inline_ "")  (progn (setq spnts_ (cdr spnts_))
                              (setq spnts_ (cons p_ spnts_))
                       ) 
                       (progn (setq ilst_ (cons inline_ ilst_))
                              (setq olst_ (cons outline_ olst_))
                              (setq spnts_ (cons p_ spnts_))
                              (setq wch_ (1+ wch_))
                              (setq inline_ "")
                              (setq outline_ "")
                       )
    )
)

(defun direct_ ()
 (setq  inline_ (strcat  inline_ (chr 127) (chr g)))
 (setq outline_ (strcat outline_ (chr 127) (chr g)))
 (wrtr_)
)

(defun keyboard_ ()
    (setq g (cadr inp_))
    (cond ((= g 13)          (ret_))
          ((= g 8)           (bsp_))
          ((= g 32)       (direct_))
          ((member g number_) (num_))
          ((member g lett_) (litra_))
          (t                (litra_))
    )
)

(defun tie_ ()
    (setq blp_ (getvar "BLIPMODE" )) (setvar "BLIPMODE"  0)
    (setq hgh_ (getvar "HIGHLIGHT")) (setvar "HIGHLIGHT" 0)
    (setq lim_ (getvar "LIMCHECK" )) (setvar "LIMCHECK"  0)
    (write-line "\nText: ")
    (command "text" p_ size_ ang_ (strcat (chr 127) (chr 45)))
    (setq lett_ '(104 102 106 101  91 112 111  93  92 96 118  46 115  97 119 
                 113  39 117 121 116 114  59 103 108 107 105  44 100 109 122  
                  99  98  72  71  95  47 110  66  78 120  74  33  34  35  36  
                  37  40  41  42  43  45  58  60  61  62  63  64  65  73  75  
                  79  80  94 125  123 81  87 126  88  90  83))

    (setq precat_ '(102 106 101  91 112 111 115  97 119 113 39 47 117 121 
                    116 114  59 103 108 107 105 100 122  95 74))
    (setq number_ '(38  48  49  50  51  52  53  54  55  56  57))
    (setq ilst_ () olst_ () spnts_ (list p_) wch_ 0 inline_ "" outline_ "")
    (setq sustain_ 1)
    (while (not (= sustain_ 0))
           (setq inp_ (grread))
           (cond ((= 2 (car inp_)) (keyboard_))
                 ((= 3 (car inp_)) (pointer_))
                 (t t)
           ) 
     )
)

(defun phsr_ (msg_)
       (setq p_ (getpoint msg_))
       (prompt (strcat "\nHeight<" (rtos (getvar "TEXTSIZE")) ">: "))
       (setq size_ (getdist p_))
       (if (null size_) (setq size_ (getvar "TEXTSIZE")))
       (setq gang_ (getangle p_ "\nRotation<0>: "))
       (if (null gang_) (setq gang_ pi ang_ 0)
                      (setq ang_ (- (* 180 (/ gang_ pi)) 180))
       )
)

(defun layout_ ()
       (cond ((= format_ "Align" ) (align_) )
             ((= format_ "Center") (center_))
             ((= format_ "Fit"   ) (fit_)   )
             ((= format_ "Middle") (middle_))
       )
)

(defun start_ ()
       (setq p_ format_)
       (prompt (strcat "\nHeight<" (rtos (getvar "TEXTSIZE")) ">: "))
       (setq size_ (getdist p_))
       (if (null size_) (setq size_ (getvar "TEXTSIZE")))
       (setq gang_ (getangle p_ "\nRotation<0>: "))
       (if (null gang_) (setq gang_ pi ang_ 0)
                      (setq ang_ (- (* 180 (/ gang_ pi)) 180))
       )
       (setq final_ '(command "TEXT" p_ size_ ang_ txt))
)

(defun center_ (/ tpr_)
       (setq tpr_ "\nCenter point: ")
       (setq final_ '(command "TEXT" "C" p_ size_ ang_ txt))
       (setq et_ (entlast))
       (phsr_ tpr_)
)

(defun centout_ (/ ncnt_)
       (lefin_)
;       (setq ncnt_ 0)
;       (repeat wch_
;               (setq et2_ (entnext et_))
;               (if (null et2_) (setq et2_ (entnext)))
;               (setq fp (cdr (assoc 11 (entget et2_))))
;               (setq sp (cdr (assoc 10 (entget et2_))))
;               (setq wp (polar fp (angle sp fp) (distance sp fp)))
;               (setq txt (nth ncnt_ olst_))
;               (command "TEXT" sp size_ ang_ txt)
;               (setq ncnt_ (1+ ncnt_))
;               (entdel et2_)
;       )
)

(defun middle_ (/ tpr_)
       (setq tpr_ "\nMiddle point: ")
       (setq final_ '(command "TEXT" "M" p_ size_ ang_ txt))
       (phsr_ tpr_)
)


(defun layout_ ()
       (cond ((= format_ "Center") (center_))
             ((= format_ "Align" ) (align_) )
             ((= format_ "Middle") (middle_))
             ((= format_ "Fit"   ) (fit_)   )

       )
)       

(defun setstyle_ (st)
       (if (= st "Simple") (setq shfl "ARABIC1" stijl_ 1)
                           (setq shfl "ARABIC2" stijl_ 2)
       )
       (command "STYLE" st shfl 0 1 0 "n" "n")
)

(defun C:ARBTXT ()
 (setq cm (getvar "CMDECHO")) ;(setvar "cmdecho" 0)
 (cond 
 ((= fnt_name "roms_bas")   (setq fnt "Baseet" fnt_file "romans,baseet"))
 ((= fnt_name "roms_sahl")  (setq fnt "Sahl"   fnt_file "romans,sahl"  ))
 ((= fnt_name "roms_nas1")  (setq fnt "Naskh1" fnt_file "romans,naskho"))
 ((= fnt_name "roms_nas2")  (setq fnt "nAskh2" fnt_file "romans,naskh2"))
 ((= fnt_name "roms_kufi1") (setq fnt "Kufi"   fnt_file "romans,kufi"  ))
 ((= fnt_name "roms_kufi2") (setq fnt "kUfi2"  fnt_file "romans,kufi2" ))
 ((= fnt_name "roms_mism")  (setq fnt "Mismar" fnt_file "romans,mismar"))
 ((= fnt_name "roms_thulth")(setq fnt "Thulth" fnt_file "romans,thulth"))
 (T     (setq fnt "Baseet" fnt_name "roms_bas" fnt_file "romans,baseet"))
 );cond
 (prompt (strcat "Baseet/Sahl/Nashk1/nAskh2/Kufi1/kUfi2/Mismar/Thulth<" 
  fnt ">: ")
 )
 (initget "Hassan Baseet Sahl Naskh1 nAskh2 Kufi1 kUfi2 Mismar Thulth")
 (setq fnt (getkword))
 (cond
 ((= fnt "Hassan")(setq fnt_name "roms_has" fnt_file "romans,hassano")
  (command "STYLE" fnt_name fnt_file 0 1 0 "n" "n"))
 ((= fnt "Baseet")(setq fnt_name "roms_bas" fnt_file "romans,baseet")
  (command "STYLE" fnt_name fnt_file 0 1 0 "n" "n"))
 ((= fnt "Sahl")(setq fnt_name "roms_sahl" fnt_file "romans,sahl"  )
  (command "STYLE" fnt_name fnt_file 0 1 0 "n" "n"))
 ((= fnt "Naskh1")(setq fnt_name "roms_nas1" fnt_file "romans,naskho")
  (command "STYLE" fnt_name fnt_file 0 1 0 "n" "n"))
 ((= fnt "nAskh2")(setq fnt_name "roms_nas2" fnt_file "romans,naskh2")
  (command "STYLE" fnt_name fnt_file 0 1 0 "n" "n"))
 ((= fnt "Kufi1")(setq fnt_name "roms_kufi1" fnt_file "romans,kufi"  )
  (command "STYLE" fnt_name fnt_file 0 1 0 "n" "n"))
 ((= fnt "kUfi2")(setq fnt_name "roms_kufi2" fnt_file "romans,kufi2" )
  (command "STYLE" fnt_name fnt_file 0 1 0 "n" "n"))
 ((= fnt "Mismar")(setq fnt_name "roms_mism" fnt_file "romans,mismar")
  (command "STYLE" fnt_name fnt_file 0 1 0 "n" "n"))
 ((= fnt "Thulth")(setq fnt_name "roms_thulth" fnt_file "romans,thulth")
  (command "STYLE" fnt_name fnt_file 0 1 0 "n" "n"))
 (T (princ))                
 );cond
 (initget "Align Center Fit Middle")
 (setq format_ 
  (getpoint "start point or Align/Center/Fit/middle_<start>: ")
 )
 (if (= (type format_) 'LIST) (start_) (layout_))
 (tie_)
 (renviron_)
 (princ)
)

(vmon)

(defun renviron ()
       (setvar "BLIPMODE" blp)
       (setvar "HIGHLIGHT" hgh)
       (setvar "LIMCHECK" lim)
)

(defun *ERROR* (s)
       (repeat (1+ wch) (entdel (entlast)))
       (renviron)
)

(defun wrtr()
       (entdel (entlast))
       (setq ptl (strcat outline (chr 219)))
       (command "text" p size ang ptl)
)

(defun counter (/ tcnt)
         (setq cntr 0)
         (setq tcnt "1")
         (while (member (ascii tcnt) number)
            (setq tcnt (substr inline (- (strlen inline) cntr) 1))
            (setq cntr (1+ cntr))
         )
         (setq cntr (1- cntr))
)

(defun drct()
      (setq inline (strcat inline (chr g)))
      (setq outline (strcat outline (chr g)))
)

(defun adnum (/ ln bgn edn sdr ajz)
         (setq ln (strlen inline))
         (setq bgn (substr inline 1 (- ln cntr)))
         (setq edn (substr inline (1+ (- ln cntr)) cntr))
         (setq sdr (substr outline 1 (- ln cntr)))
         (setq ajz (substr outline (1+ (- ln cntr)) cntr))
         (setq inline (strcat bgn (chr g) edn))
         (setq outline (strcat sdr (chr g) ajz))
)

(defun shift ()
         (setq inline (strcat (chr g) inline))
         (setq outline (strcat (chr g) outline))
)

(defun num ()
         (counter)
         (cond ((= cntr 0) (drct))
               ((= cntr (strlen inline)) (shift))
               (t (adnum))
         )
         (wrtr)
)

(defun find(asky loc)
       (cond ((not (member asky lett)) asky)
             ((= asky 104) (nth loc '(101 102 102 101)))
             ((= asky 102) (nth loc '(103 104 105 106)))
             ((= asky 106) (nth loc '(107 108 109 110)))
             ((= asky 101) (nth loc '(111 112 113 114)))
             ((= asky  91) (nth loc '(115 116 117 118)))
             ((= asky 112) (nth loc '(119 220 121 122)))
             ((= asky 111) (nth loc '(123 124 125 126)))
             ((= asky  93) (nth loc '(127 128 128 127)))
             ((= asky  92) (nth loc '(129 130 130 129)))
             ((= asky 118) (nth loc '(131 132 132 131)))
             ((= asky  46) (nth loc '(133 134 134 133)))
             ((= asky 115) (nth loc '(135 136 137 138)))
             ((= asky  97) (nth loc '(139 140 141 142)))
             ((= asky 119) (nth loc '(143 144 145 146)))
             ((= asky 113) (nth loc '(147 148 149 150)))
             ((= asky  39) (nth loc '(151 152 153 154)))
             ((= asky  47) (nth loc '(155 156 157 158)))
             ((= asky 117) (nth loc '(159 160 161 162)))
             ((= asky 121) (nth loc '(163 164 165 166)))
             ((= asky 116) (nth loc '(167 168 169 170)))
             ((= asky 114) (nth loc '(171 172 173 174)))
             ((= asky  59) (nth loc '(175 176 177 178)))
             ((= asky 103) (nth loc '(179 180 181 182)))
             ((= asky 108) (nth loc '(183 184 185 186)))
             ((= asky 107) (nth loc '(187 188 189 190)))
             ((= asky 105) (nth loc '(191 192 193 194)))
             ((= asky  44) (nth loc '(195 196 196 195)))
             ((= asky 100) (nth loc '(197 198 199 200)))
             ((= asky 109) (nth loc '(201 202 202 201)))
             ((= asky 122) (nth loc '(203 204 205 206)))
             ((= asky  99) (nth loc '(207 208 208 207)))
             ((= asky  98) (nth loc '(209 210 210 209)))
             ((= asky  72) (nth loc '(211 212 212 211)))
             ((= asky  71) (nth loc '(213 214 214 213)))
             ((= asky 110) (nth loc '(216 215 215 216)))
             ((= asky  95) (nth loc '(95 96 97 98)))
       )
)

(defun prune (/ dg ct term)
     (setq dg (ascii (substr inline (strlen inline) 1)))
     (setq ct (if (member (ascii (substr inline (1- (strlen inline)) 1))
                          precat) 2 3))
     (setq term (chr (find dg ct)))
     (setq outline (strcat (substr outline 1 (- (strlen outline) 2)) term))
)

(defun duo (/ ct term)
     (setq ct (if (member (ascii (substr inline 1 1)) precat) 2 3))
     (setq term (chr (find (ascii (substr inline 2 1)) ct)))
     (setq outline (strcat (substr outline 1 1) term))
)

(defun una ()
     (setq outline (chr (find (ascii inline) 3)))
)

(defun deleter ()
     (setq inline (substr inline 1 (1- (strlen inline))))
     (cond ((= (strlen inline) 1) (una))
           ((= (strlen inline) 2) (duo))
           (t (prune))
     )
)

(defun chop ()
    (setq inline (substr inline 1 (1- (strlen inline))))
    (setq outline (substr outline 1 (1- (strlen outline))))
)

(defun denumber (/ ln bgn edn sdr ajz)
        (counter)
        (if (= cntr (strlen inline))
            (progn
               (setq inline (substr inline 2 (1- (strlen inline))))
               (setq outline (substr outline 2 (1- (strlen outline))))
            )
            (progn
               (setq ln (strlen inline))
               (setq bgn (substr inline 1 (- ln cntr)))
               (setq edn (substr inline (+ 2 (- ln cntr)) (1- cntr)))
               (setq sdr (substr outline 1 (- ln cntr)))
               (setq ajz (substr outline (+ 2 (- ln cntr)) (1- cntr)))
               (setq inline (strcat bgn edn))
               (setq outline (strcat sdr ajz))
            )
         )
)

(defun debranch (/ br)
      (setq br (ascii (substr inline (strlen inline) 1)))
      (cond ((member br number) (denumber))
            ((member br sym) (chop))
            ((member br lett) (deleter))
      )
)

(defun vanish ()
       (setq inline "")
       (setq outline "")
)

(defun up ()
       (if (= wch 0) t
           (progn
                (entdel (entlast))
                (setq wch (1- wch))
                (setq inline (car ilst)) (setq ilst (cdr ilst))
                (setq outline (car olst)) (setq olst (cdr olst))
                (setq spnts (cdr spnts)) (setq p (car spnts))
           )
        )
)

(defun bsp ()
       (cond ((= (strlen inline) 0) (up))
             ((= (strlen inline) 1) (vanish))
             (t (debranch))
       )
       (wrtr)
)

(defun second(/ ps fchar schar)
       (setq inline (strcat inline (chr g)))
       (setq ps (if (member (ascii inline) precat) 2 3))
       (setq fchar (chr (find (ascii inline) 0)))
       (setq schar (chr (find g ps)))
       (setq outline (strcat fchar schar))
)

(defun first()
       (setq inline (strcat inline (chr g)))
       (setq outline (chr (find g 3)))
)

(defun strngr(/ last posg blast posl one two)
       (setq last (ascii (substr inline (strlen inline) 1)))
       (setq posg (if (member last precat) 2 3))
       (setq blast (ascii (substr inline (1- (strlen inline)) 1)))
       (setq posl (if (member blast precat) 1 0))
       (setq one (chr (find last posl)))
       (setq two (chr (find g posg)))
       (setq inline (strcat inline (chr g)))
       (setq outline (strcat (substr outline 1 (1- (strlen outline))) one
       two))
)

(defun direct()
      (setq inline (strcat inline (chr g)))
      (setq outline (strcat outline (chr g)))
      (wrtr)
)

(defun letra ()
       (cond ((= (strlen inline) 0) (first))
             ((= (strlen inline) 1) (second))
             (t (strngr))
       )
       (wrtr)
)

(defun lefin (/ numero)
       (repeat (1+ wch) (entdel (entlast)))
       (setq olst (reverse olst))
       (setq spnts (reverse (cdr spnts)))
       (setq numero 0)
       (repeat wch
               (setq p (nth numero spnts))
               (setq txt (nth numero olst))
               (eval final)
               (setq numero (1+ numero))
       )
       (setq sustain 0)
)

(defun getout ()
       (cond ((= format "Center") (centout))
             ((= format "Middle") (midout))
             ((= (type format) 'LIST) (lefin))
       )
)

(defun ret ()
      (if (= (strlen inline) 0) (getout)
             (progn
                  (entdel (entlast))
                  (command "text" p size ang outline)
                  (setq ilst (cons inline ilst))
                  (setq olst (cons outline olst))
                  (setq p (polar p (+ gang (/ pi 2)) (* 2 size)))
                  (setq spnts (cons p spnts))
                  (setq wch (1+ wch))
                  (command "text" p size ang (chr 219))
                  (setq inline "")
                  (setq outline "")
             )
       )
)

(defun pointer ()
    (entdel (entlast))
    (command "text" p size ang outline)
    (setq p (cadr inp))
    (command "text" p size ang (chr 219))
    (if (= inline "")  (progn (setq spnts (cdr spnts))
                              (setq spnts (cons p spnts))
                       ) 
                       (progn (setq ilst (cons inline ilst))
                              (setq olst (cons outline olst))
                              (setq spnts (cons p spnts))
                              (setq wch (1+ wch))
                              (setq inline "")
                              (setq outline "")
                       )
    )
)

(defun keyboard ()
    (setq g (cadr inp))
    (cond ((= g 13) (ret))
          ((= g 8) (bsp))
          ((member g number) (num))
          ((member g sym) (direct))
          ((member g lett) (letra))
          (t t)
    )
)

(defun tie ()
    (setq blp (getvar "BLIPMODE" )) (setvar "BLIPMODE" 0)
    (setq hgh (getvar "HIGHLIGHT" )) (setvar "HIGHLIGHT" 0)
    (setq lim (getvar "LIMCHECK" )) (setvar "LIMCHECK" 0)
    (write-line "\nText: ")
    (command "text" p size ang (chr 219))
    (setq lett '(104 102 106 101 91 112 111 93 92 96 118 46 115 97 119 113 39
                 117 121 116 114 59 103 108 107 105 44 100 109 122 99 98 72 71
                 95 47 110))
    (setq precat '(102 106 101 91 112 111 115 97 119 113 39 47 117 121 116 114
                   59 103 108 107 105 100 122 95 ))
    (setq number '(38 48 49 50 51 52 53 54 55 56 57))
    (setq sym '(41 40 75 45 43 42 60 62 63 33 37 32 120))
    (setq ilst () olst () spnts (list p) wch 0 inline "" outline "")
    (setq sustain 1)
    (while (not (= sustain 0))
           (setq inp (grread))
           (cond ((= 2 (car inp)) (keyboard))
                 ((= 3 (car inp)) (pointer))
                 (t t)
           ) 
     )
)

(defun phsr (msg)
       (setq p (getpoint msg))
       (prompt (strcat "\nHeight<" (rtos (getvar "TEXTSIZE")) ">: "))
       (setq size (getdist p))
       (if (null size) (setq size (getvar "TEXTSIZE")))
       (setq gang (getangle p "\nRotation<0>: "))
       (if (null gang) (setq gang pi ang 0)
                      (setq ang (- (* 180 (/ gang pi)) 180))
       )
)

(defun layout ()
       (cond ((= format "Align") (align))
             ((= format "Center") (center))
             ((= format "Fit") (fit))
             ((= format "Middle") (middle))
       )
)

(defun start ()
       (setq p format)
       (prompt (strcat "\nHeight<" (rtos (getvar "TEXTSIZE")) ">: "))
       (setq size (getdist p))
       (if (null size) (setq size (getvar "TEXTSIZE")))
       (setq gang (getangle p "\nRotation<0>: "))
       (if (null gang) (setq gang pi ang 0)
                      (setq ang (- (* 180 (/ gang pi)) 180))
       )
       (setq final '(command "TEXT" p size ang txt))
)

(defun center (/ tpr)
       (setq tpr "\nCenter point: ")
       (setq final '(command "TEXT" "C" p size ang txt))
       (setq et (entlast))
       (phsr tpr)
)

(defun centout (/ ncnt)
       (lefin)
;       (setq ncnt 0)
;       (repeat wch
;               (setq et2 (entnext et))
;               (if (null et2) (setq et2 (entnext)))
;               (setq fp (cdr (assoc 11 (entget et2))))
;               (setq sp (cdr (assoc 10 (entget et2))))
;               (setq wp (polar fp (angle sp fp) (distance sp fp)))
;               (setq txt (nth ncnt olst))
;               (command "TEXT" sp size ang txt)
;               (setq ncnt (1+ ncnt))
;               (entdel et2)
;       )
)

(defun middle (/ tpr)
       (setq tpr "\nMiddle point: ")
       (setq final '(command "TEXT" "M" p size ang txt))
       (phsr tpr)
)


(defun layout ()
       (cond ((= format "Center") (center))
             ((= format "Align") (align))
             ((= format "Middle") (middle))
             ((= format "Fit") (fit))

       )
)       

(defun setstyle (st)
       (if (= st "Simple") (setq shfl "ARABIC1" stijl 1)
                           (setq shfl "ARABIC2" stijl 2)
       )
       (command "STYLE" st shfl 0 1 0 "n" "n")
)

(defun C:ARABIC ()
       (setvar "cmdecho" 0)
       (cond ((= stijl nil) (setq stylprmt "Simple"))
             ((= stijl 1)  (setq stylprmt "Simple"))
             ((= stijl 2)  (setq stylprmt "Complex"))
       )
       (prompt (strcat "Simple/Complex/Adjust<" stylprmt ">: "))
       (initget "Simple Complex Adjust")
       (setq stylch (getkword))
       (cond ((and (= stijl nil) (= stylch nil))
                   (progn                  
                          (command "STYLE" "Simple" "ARABIC1" 0 1 0 "n" "n"))
                          (setq stijl 1)
                   )
             ((and (or (= stijl nil) (= stijl 1)) (= stylch "Complex")) 
                                                    (setstyle stylch))
             ((and (= stijl 2) (= stylch "Simple")) (setstyle stylch))
             ((= stylch nil) t)
       )
       (initget "Align Center Fit Middle")
       (setq format 
             (getpoint "Startpoint or Align/Center/Fit/Middle<Start>: "))
       (if (= (type format) 'LIST) (start) (layout))
       (tie)
       (renviron)
       (princ)
)
